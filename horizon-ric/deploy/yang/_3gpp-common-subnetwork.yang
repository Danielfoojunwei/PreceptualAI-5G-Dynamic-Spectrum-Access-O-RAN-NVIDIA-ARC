module _3gpp-common-subnetwork {
  yang-version 1.1;
  namespace "urn:3gpp:sa5:_3gpp-common-subnetwork";
  prefix "subnet3gpp";
    
  import _3gpp-common-yang-types { prefix types3gpp; }
  import _3gpp-common-yang-extensions { prefix yext3gpp ; }
  import _3gpp-common-top { prefix top3gpp; }
  import _3gpp-common-measurements { prefix meas3gpp; }
  import _3gpp-common-subscription-control { prefix subscr3gpp; }
  import _3gpp-common-fm { prefix fm3gpp; }
  import _3gpp-common-trace { prefix trace3gpp; }
  import ietf-yang-schema-mount { prefix yangmnt; }
  import _3gpp-common-files { prefix files3gpp; }
  import _3gpp-5gc-nrm-configurable5qiset { prefix fiveqi3gpp; }
  import _3gpp-5gc-nrm-ecmconnectioninfo { prefix econn3gpp ; }
  import _3gpp-nr-nrm-ecmappingrule { prefix ecmap3gpp ; }

  organization "3GPP SA5";
  contact "https://www.3gpp.org/DynaReport/TSG-WG--S5--officials.htm?Itemid=464";
    
  description "Defines basic SubNetwork which will be augmented by other IOCs
    Copyright 2025, 3GPP Organizational Partners (ARIB, ATIS, CCSA, ETSI, TSDSI, 
    TTA, TTC). All rights reserved.";
  reference "3GPP TS 28.623
      Generic Network Resource Model (NRM)
      Integration Reference Point (IRP);
      Solution Set (SS) definitions
      
      3GPP TS 28.622
      Generic Network Resource Model (NRM)
      Integration Reference Point (IRP);
      Information Service (IS)
      
      3GPP TS 28.620 
      Umbrella Information Model (UIM)";
  
  revision 2025-03-24 { reference "CR-0517 CR0526"; } 
  revision 2024-08-18 { reference CR-1336 ; } 
  revision 2024-01-30 { reference CR-0328 ; } 
  revision 2023-11-14 { reference CR-0305 ; } 
  revision 2023-09-18 { reference CR-0271 ; } 
  revision 2023-08-10 { reference CR-0257;   }
  revision 2023-04-26 { reference CR-0250; }
  revision 2023-02-14 { reference CR-0234; }
  revision 2022-09-30 { reference CR-0191 ; }
  revision 2021-01-16 { reference "CR-0120"; }  
  revision 2020-08-06 { reference "CR-0102"; }  
  revision 2020-06-08 { reference "CR-0092"; }  
  revision 2020-05-08 {
    reference "S5-203316";
  }

    
  revision 2020-03-11 { 
    description "Added KPIs and corrections";
    reference "S5-201365, S5-201581, SP-200229";
  }

  revision 2020-02-24 {
    reference "S5-201365";
  }

  revision 2019-06-17 {
    reference "Initial revision";
  }

  feature ECMappingRuleUnderSubNetwork {
    description "ECMappingRule shall be contained under SubNetwork.";
  }
  
  feature EcmConnectionInfoUnderSubNetwork {
    description "The EcmConnectionInfo shall be contained under
    Subnetwork";
  }

  feature Configurable5QISetUnderSubNetwork {
    description "The Configurable5QISet shall be contained under
    Subnetwork";
  }

  feature FilesUnderSubNetwork {
    description "Files shall be contained under Subnetwork";
  }

  feature ExternalsUnderSubNetwork {
    description "Classes representing external entities like EUtranFrequency, 
      ExternalGNBCUCPFunction, ExternalENBFunction 
      are contained under a Subnetwork list/class.";
  }
  
  feature MeasurementsUnderSubNetwork {
    description "The MeasurementSubtree shall be contained under SubNetwork";
  }
  
  feature SubscriptionControlUnderSubNetwork {
    description "The SubscriptionControlSubtree shall be contained under
      SubNetwork";
  }

  feature SupportedNotificationsUnderSubNetwork {
    description "The SupportedNotificationsSubtree shall be contained under
      SubNetwork";
  }

  feature FmUnderSubNetwork {
    description "The FmSubtree shall be contained under SubNetwork";
  }
  
  feature TraceUnderSubNetwork {
    description "The TraceSubtree shall be contained under SubNetwork";
  }
  
  feature DESManagementFunction {
    description "Class representing Distributed SON or Domain-Centralized SON
      Energy Saving feature. The DESManagementFunction shall be contained under
      SubNetwork.";
  }
 
  feature DMROFunction {
    description "Class representing D-SON function of MRO feature. The
      DMROFunction shall be contained under SubNetwork.";
  }
  
  feature DRACHOptimizationFunction {
    description "Class representing D-SON function of RACH optimization feature.
      The DRACHOptimizationFunction shall be contained under SubNetwork.";
  }
  
  feature DPCIConfigurationFunction {
    description "Class representing Distributed SON or Domain-Centralized SON
      function of PCI configuration feature. The DPCIConfigurationFunction shall
      be contained under SubNetwork.";
  }
  
  feature CPCIConfigurationFunction {
    description "Class representing Cross Domain-Centralized SON function of PCI
      configuration feature. The CPCIConfigurationFunction shall be contained
      under SubNetwork.";
  }
  
  feature CESManagementFunction {
    description "Class representing Cross Domain-Centralized SON Energy Saving
      feature. The CESManagementFunction shall be contained under SubNetwork.";
  }

  grouping Domain_Grp {
    description "A domain is a partition of instances of managed entities 
      such that : 
      -  the group represents a topological structure which describes the 
      potential for connectivity
      -  Subject to common administration
      -  With common characteristics";
    
    leaf dnPrefix {
      type types3gpp:DistinguishedName;
      yext3gpp:inVariant;      
      reference "Annex C of 32.300 ";
    }
    
    leaf userLabel {
        type string;
        description "A user-friendly (and user assignable) name of this object.";
    }
    
    leaf userDefinedNetworkType {
      type string;
      description "Textual information indicating network type, e.g. 'UTRAN'.";
    }    
  }

  grouping SubNetworkGrp {
    uses Domain_Grp;
      
    leaf-list setOfMcc {
      description "Set of Mobile Country Code (MCC). 
        The MCC uniquely identifies the country of domicile 
        of the mobile subscriber. MCC is part of the IMSI (3GPP TS 23.003)

        This list contains all the MCC values in subordinate object 
        instances to this SubNetwork instance.

        See clause 2.3 of 3GPP TS 23.003 for MCC allocation principles.

        It shall be supported if there is more than one value in setOfMcc 
        of the SubNetwork. Otherwise the support is optional.";            
      type types3gpp:Mcc;
    }

    leaf priorityLabel {
      mandatory true;
      type uint32;
    }
    
    uses meas3gpp:SupportedPerfMetricGroupGrp;

    leaf-list supportedTraceMetrics {
      type string;
      config false;
      description "List of trace metrics. When this attribute is contained in 
        a managed object it defines the trace metrics supported for this 
        object and all descendant objects.

        Trace metrics include trace messages, MDT measurements 
        (Immediate MDT, Logged MDT, Logged MBSFN MDT), RLF and RCEF reports, 
        see TS 32.422. Trace metrics are identified with their metric 
        identifier. The metric identifier is constructed as defined 
        in clause 10 of TS 32.422.";
    }
  }    

  list SubNetwork {
    key id;
    description "Represents a set of managed entities
      Contained ManagedElements and SubNetworks shall be connected via 
      YANG Schema-mount.";

    uses top3gpp:Top_Grp;
    container attributes {    
      uses SubNetworkGrp;
    }
        
    uses meas3gpp:MeasurementSubtree {
      if-feature MeasurementsUnderSubNetwork;
    }

    uses subscr3gpp:SubscriptionControlSubtree {
      if-feature SubscriptionControlUnderSubNetwork;
    }

    uses subscr3gpp:SupportedNotificationsSubtree {
      if-feature SupportedNotificationsUnderSubNetwork;
    }

    uses fm3gpp:FmSubtree {
      if-feature FmUnderSubNetwork;
    }
    
    uses trace3gpp:TraceSubtree {
      if-feature TraceUnderSubNetwork;
    }

    uses files3gpp:FilesSubtree {
      if-feature FilesUnderSubNetwork;
    }  

    uses fiveqi3gpp:Configurable5QISetSubtree {
      if-feature Configurable5QISetUnderSubNetwork;
    }

    uses econn3gpp:EcmConnectionInfoSubtree {
      if-feature EcmConnectionInfoUnderSubNetwork;
    }

    yangmnt:mount-point children-of-SubNetwork {
      description "Mountpoint for contained ManagedElements and SubNetworks";
      reference "RFC8528 YANG Schema Mount";
    }
    
    uses ecmap3gpp:NRECMappingRuleSubtree {
      if-feature EcmConnectionInfoUnderSubNetwork;
    }
    
    // augment external parts here
  }
}
